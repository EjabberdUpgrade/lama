ORG-LAMA-MIB DEFINITIONS ::= BEGIN

IMPORTS
        OBJECT-GROUP, NOTIFICATION-GROUP
                FROM SNMPv2-CONF
        DisplayString
                FROM SNMPv2-TC
        otp, storm
                FROM ORG-TC
        TimeTicks, OBJECT-TYPE, MODULE-IDENTITY, NOTIFICATION-TYPE,
        Counter32, Gauge32, Integer32
                FROM SNMPv2-SMI;

-- 1.3.6.1.4.1.14627.10.1.10
lama    MODULE-IDENTITY
        LAST-UPDATED "200603200000Z"
        ORGANIZATION "Generic"
        CONTACT-INFO
                "Serge Aleynikov (saleyn@gmail.com)"
        DESCRIPTION
                "Log and Alarm Management application's MIB."
        ::= { otp 10 }

-- 1.3.6.1.4.1.14627.10.1.10.1
lamaObjects
        OBJECT IDENTIFIER ::= { lama 1 }
lamaConformance
        OBJECT IDENTIFIER ::= { lama 2 }
lamaTraps
        OBJECT IDENTIFIER ::= { lama 3 }

--
-- Node definitions
--

-- 1.3.6.1.4.1.14627.10.1.10.1.1
lamaNodeName OBJECT-TYPE
        SYNTAX      DisplayString
        MAX-ACCESS  read-only
        STATUS      current
        DESCRIPTION "The symbolic name of the erlang node."
        ::= { lamaObjects 1 }

-- 1.3.6.1.4.1.14627.10.1.10.1.2
lamaDateTime OBJECT-TYPE
        SYNTAX      DisplayString
        MAX-ACCESS  read-only
        STATUS      current
        DESCRIPTION "Node's current date and time info."
        ::= { lamaObjects 2 }

-- 1.3.6.1.4.1.14627.10.1.10.1.3
lamaCurrentAlarmCount OBJECT-TYPE
        SYNTAX      Gauge32
        MAX-ACCESS  read-only
        STATUS      current
        DESCRIPTION "Number of currently active alarms in the system."
        ::= { lamaObjects 3 }

-- 1.3.6.1.4.1.14627.10.1.10.1.4
lamaAlarmInformation OBJECT-TYPE
        SYNTAX      DisplayString
        MAX-ACCESS  read-only
        STATUS      current
        DESCRIPTION "Additional information pin-pointing the problem."
        ::= { lamaObjects 4 }

-- 1.3.6.1.4.1.14627.10.1.10.1.5
clearedAlarmObject OBJECT-TYPE
        SYNTAX      OBJECT IDENTIFIER
        MAX-ACCESS  read-only
        STATUS      current
        DESCRIPTION
            "The cleared alarm object."
        ::= { lamaObjects 5 }

-- Alarms

-- 1.3.6.1.4.1.14627.10.1.10.3.1
lamaAlarmCleared NOTIFICATION-TYPE
        OBJECTS {
            lamaAlarmInformation,
            lamaDateTime,
            clearedAlarmObject
        }
        STATUS  current
        DESCRIPTION
          "This event is sent when an alarm has been cleared,
           either by the application or by an operator."
        ::= { lamaTraps 1 }

-- 1.3.6.1.4.1.14627.10.1.10.3.2
loadSystemMemoryHighAlarm NOTIFICATION-TYPE
    OBJECTS {
        lamaNodeName
        }
    STATUS  current
    DESCRIPTION
        "This alarm is sent when the used system memory exceeds
        loadMemorySystemWatermark of the total available memory.
        currentAlarmObject points to the loadSystemUsedMemory of the
        system.
        Default severity is Major."
    ::= { lamaTraps 2 }

-- 1.3.6.1.4.1.14627.10.1.10.3.3
loadErlProcMemoryHighAlarm NOTIFICATION-TYPE
    OBJECTS {
        lamaNodeName
        }
    STATUS  current
    DESCRIPTION
        "This alarm is sent when an Erlang process exceeds
        loadMemoryErlProcWatermark of the total available memory.
        currentAlarmObject points to the loadLargestErlProcess that
        is too big.
        Default severity is Minor."
    ::= { lamaTraps 3 }

-- 1.3.6.1.4.1.14627.10.1.10.3.4
diskAlmostFullAlarm NOTIFICATION-TYPE
    OBJECTS {
        lamaNodeName,
        lamaAlarmInformation
        }
    STATUS  current
    DESCRIPTION
        "Alarm which is sent if the log wraps too quickly.
        currentAlarmObject points to the diskDescr of the faulty disk.
        Default severity is Major."
    ::= { lamaTraps 4 }

-- conformance information

-- 1.3.6.1.4.1.14627.10.1.10.2.1
lamaObjectsGroup OBJECT-GROUP
        OBJECTS {
            lamaNodeName,
            lamaDateTime,
            lamaCurrentAlarmCount,
            lamaAlarmInformation,
            clearedAlarmObject
        }
        STATUS current
        DESCRIPTION
                "Group of LAMA objects"
        ::= { lamaConformance 1 }

-- 1.3.6.1.4.1.14627.10.1.10.2.2
lamaTrapsGroup NOTIFICATION-GROUP
        NOTIFICATIONS {
            lamaAlarmCleared,
            loadSystemMemoryHighAlarm,
            loadErlProcMemoryHighAlarm,
            diskAlmostFullAlarm
        }
        STATUS current
        DESCRIPTION
                "Group of LAMA traps"
        ::= { lamaConformance 2 }

END

--
-- ORG-LAMA-MIB.mib
--
